# ドアロック制御ソフト要求仕様_theirs

## ドアロック制御ソフト要求仕様: ドアロック制御ソフト要求仕様.docx からインポート済み (Functional)
Microsoft Word からインポート済み
C:\Users\tliang\Desktop\Task\Customer Visit\Honda\171003_SLVV transition_SLCK_SLRQ\EmbSW_MBD_Demo\ドアロック制御ソフト要求仕様.docx

### 1. 制御周期　[REQ1]: 制御周期 REQ1 (Functional)
1. 制御周期 [REQ1]
l 100ms周期タスクとして実行する

### 2. 前提条件　[REQ2]: 前提条件 REQ2 (Functional)
2. 前提条件 [REQ2]
l 自動車の2ドアクーペのドアロックを対象とした自動制御システムとする
l ドアのロック/アンロックは制御指令値を基に外部処理でアクチュエータを駆動する
(本制御ではアクチュエータを駆動させるための電圧出力の制御はおこなわない)

### 3. 初期化　[REQ3]: 初期化 REQ3 (Functional)
3. 初期化 [REQ3]
l 各ドアがアンロックの状態から制御を開始する

### 4. 制御指令算出機能　[REQ4]: 制御指令算出機能 REQ4 (Functional)
4. 制御指令算出機能 [REQ4]
l エンジンが動作している かつ 車両速度が2秒間以上、5km/hを超えている場合を車両走行開始時と判断し、ロック指令を出力する
l エアバッグが作動した場合を車両異常と判断し、アンロック指令を出力する

### 5. 診断機能　[REQ5]: 診断機能 REQ5 (Functional)
5. 診断機能 [REQ5]
l 各ドアのロック用アクチュエータの作動位置に応じて、各ドアのロック状態を判定する
Ø 作動位置が12mm未満 : アンロック
Ø 作動位置が4mm越え：ロック
Ø 上記以外：ニュートラル (ロック ⇔ アンロックに移行中の状態)
l ロックまたはアンロックの制御指令から2秒後のドアのロック状態に基づいて、異常を判定する
| 制御指令 | 指令2秒後のドアのロック状態 | 診断 |
| --- | --- | --- |
| ロック | ロック | NORMAL |
|  | ロック以外 | FAIL |
| アンロック | アンロック | NORMAL |
|  | アンロック以外 | FAIL |
Ø FAILと判定した場合は、それ以降の故障診断は実行しない(故障診断結果はクリアしない)
Ø 故障判定されていない場合、故障診断は制御指令状態が変わるたび(アンロック→ロック、 ロック→アンロック)に実施する

### 6. 入出力インターフェース　[REQ6]: 入出力インターフェース REQ6 (Functional)
6. 入出力インターフェース [REQ6]
l 入出力に用いるグローバル変数は次の通り
| 名前 | 入力/出力 | データ型 | 単位 | 説明 |
| --- | --- | --- | --- | --- |
| Speed | IN | single | km/h | 車速信号 |
| EngStart | IN | boolean | - | エンジン作動状態フラグ (OFF=0 / ON=1) |
| AirBagOn | IN | boolean | - | エアバッグ作動状態フラグ (OFF=0 / ON=1) |
| RightDoorPos | IN | single | cm | 右ドア用アクチュエータ作動位置 |
| LeftDoorPos | IN | single | cm | 左ドア用アクチュエータ作動位置 |
| DLockCmd | OUT | boolean | - | ロック・アンロック指令値 (アンロック指令=0 / ロック指令=1) |
| DLockDiag | OUT | enum | - | ドアロック故障診断フラグ (NORMAL / FAIL) |

### 機能テスト用タイミングチャート (Functional)
機能テスト用タイミングチャート
l NORMAL1
l NORMAL2
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l FAIL1
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l FAIL2
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