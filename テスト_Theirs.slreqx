# テスト_Theirs

## #1: 要件１ (Functional)
Diagram
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
## #2: 要件２ (Functional)
| Speed | IN | Int8 | 0~150 |
| --- | --- | --- | --- |
| Diag | IN | Boolean | True/False |
| ControlSW | OUT | Boolean | ON/OFF |

## #3: 要件３ (Functional)
memo
